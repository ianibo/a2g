ASN-USEFUL 

DEFINITIONS ::=

BEGIN

-- Antlr seems to choke on a EXTERNAL all uppper case
EXTERNAL ::= [UNIVERSAL 8] IMPLICIT SEQUENCE {
      direct-reference  OBJECT IDENTIFIER OPTIONAL,
      indirect-reference  INTEGER OPTIONAL,
      data-value-descriptor  ObjectDescriptor  OPTIONAL,
      encoding  CHOICE
                  {single-ASN1-type  [0] ANY,
                   octet-aligned     [1] IMPLICIT OCTET STRING,
                   arbitrary         [2] IMPLICIT BIT STRING}
}

END
