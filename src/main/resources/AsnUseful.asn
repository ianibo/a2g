ASN-USEFUL 

DEFINITIONS ::=

BEGIN

-- Antlr seems to choke on a EXTERNAL all uppper case
EXTERNAL ::= [UNIVERSAL 8] IMPLICIT SEQUENCE {
      direct-reference  OBJECT IDENTIFIER OPTIONAL,
      indirect-reference  INTEGER OPTIONAL,
      data-value-descriptor  ObjectDescriptor  OPTIONAL,
      encoding  CHOICE
                  {single-ASN1-type  [0] ANY,
                   octet-aligned     [1] IMPLICIT OCTET STRING,
                   arbitrary         [2] IMPLICIT BIT STRING}
}


-- NumericString ::= [UNIVERSAL 18] IMPLICIT STRING
-- PrintableString ::= [UNIVERSAL 19] IMPLICIT STRING
-- TeletexString ::= [UNIVERSAL 20] IMPLICIT STRING
-- VideotexString  ::= [UNIVERSAL 21] IMPLICIT STRING
-- VisibleString ::= [UNIVERSAL 26] IMPLICIT STRING
-- IA5String ::= [UNIVERSAL 22] IMPLICIT STRING
-- GraphicString ::= [UNIVERSAL 25] IMPLICIT STRING
-- GeneralString ::= [UNIVERSAL 27] IMPLICIT STRING

END
